# FreeCAD Macro: run-tests.FCMacro
# Runs full test suite in official FreeCAD 1.1.4 Linux GUI offscreen runner.

import gc
import importlib.util
import json
import os
import sys
import traceback
import unittest

root = os.environ.get("FF_ROOT", os.getcwd())
reports_dir = os.environ.get("FF_REPORTS", os.path.join(root, "reports"))
os.makedirs(reports_dir, exist_ok=True)
startup_log_path = os.path.join(reports_dir, "startup.log")


class ImmediateDetailsResult(unittest.TextTestResult):
    """Writes each failure's traceback as soon as the test fails, not only in the final report: a shard killed by its
    timeout never reaches that report (issue #148)."""

    def _detail(self, flavour, test, err):
        self.stream.writeln(self.separator1)
        self.stream.writeln(f"{flavour}: {self.getDescription(test)}")
        self.stream.writeln(self.separator2)
        self.stream.writeln(self._exc_info_to_string(err, test))
        self.stream.flush()

    def addFailure(self, test, err):
        super().addFailure(test, err)
        self._detail("FAIL", test, err)

    def addError(self, test, err):
        super().addError(test, err)
        self._detail("ERROR", test, err)

    def addSubTest(self, test, subtest, err):
        super().addSubTest(test, subtest, err)
        if err is not None:
            failure = issubclass(err[0], test.failureException)
            self._detail("FAIL" if failure else "ERROR", subtest, err)


def log_startup(marker: str) -> None:
    try:
        with open(startup_log_path, "a", encoding="utf-8") as f:
            f.write(f"[startup] {marker}\n")
    except Exception:
        pass


def hard_exit(code: int) -> None:
    """End FreeCAD now with code, skipping interpreter and library teardown.

    On Windows os._exit still runs DLL detach routines, where the portable FreeCAD
    build aborts with 0xC0000409 after the suite has finished, so terminate the process.
    """
    if os.name == "nt":
        import ctypes
        from ctypes import wintypes

        kernel32 = ctypes.WinDLL("kernel32", use_last_error=True)
        # HANDLE is 64-bit: without these declarations ctypes passes the -1 pseudo-handle as a
        # 32-bit int, TerminateProcess fails and os._exit aborts in the DLL teardown.
        kernel32.GetCurrentProcess.restype = wintypes.HANDLE
        kernel32.TerminateProcess.argtypes = (wintypes.HANDLE, wintypes.UINT)
        kernel32.TerminateProcess.restype = wintypes.BOOL
        if not kernel32.TerminateProcess(kernel32.GetCurrentProcess(), code):
            log_startup(f"terminate-process-failed: winerror {ctypes.get_last_error()}")
    os._exit(code)


try:
    log_startup("macro-entry")

    # Arm a one-shot stack watchdog before native imports; diagnostics are
    # best-effort and must never change test verdicts or dialog behavior.
    diagnostic_session = None
    try:
        spec = importlib.util.spec_from_file_location(
            "ci_timeout_diagnostics", os.path.join(os.path.dirname(__file__), "diagnostics.py")
        )
        diagnostics = importlib.util.module_from_spec(spec)
        spec.loader.exec_module(diagnostics)
        diagnostic_session = diagnostics.start(reports_dir)
    except Exception:
        log_startup("stack-diagnostics-unavailable")

    # 1. Import FreeCAD core modules before test suite imports
    import FreeCAD
    import FreeCADGui
    import Part

    if diagnostic_session is not None:
        try:
            from PySide import QtCore, QtWidgets

            diagnostic_session.attach_qt(QtCore, QtWidgets)
            if os.environ.get("FF_NATIVE_DIAGNOSTICS") == "1":
                diagnostics.attach_structural(diagnostic_session, QtCore, QtWidgets, reports_dir)
        except Exception:
            log_startup("modal-diagnostics-unavailable")

    # 2. Strict runtime version validation against ci/targets.json (single source of truth)
    target = os.environ.get("FF_TARGET", "stable")
    try:
        with open(os.path.join(os.path.dirname(__file__), "targets.json"), encoding="utf-8") as targets_file:
            targets = json.load(targets_file)
    except Exception as exc:
        log_startup(f"error-targets: {type(exc).__name__}")
        sys.stderr.write(f"ERROR: Cannot read ci/targets.json: {type(exc).__name__}: {exc}\n")
        sys.stderr.flush()
        hard_exit(1)

    if target not in targets:
        expected_names = " or ".join(repr(name) for name in targets)
        msg = f"ERROR: Unsupported test target '{target}'. Expected {expected_names}.\n"
        log_startup(f"error-target: {target}")
        sys.stderr.write(msg)
        sys.stderr.flush()
        hard_exit(1)

    fc_version = FreeCAD.Version()
    py_ver = sys.version_info[:2]

    expected_fc = tuple(targets[target]["expected_freecad"])
    expected_py = tuple(targets[target]["expected_python"])
    fc_text = ".".join(expected_fc)
    py_text = ".".join(str(part) for part in expected_py)
    if target == "stable":
        target_label = f"Pinned baseline {targets[target]['label']} (Python {py_text})"
    else:
        target_label = f"Pinned {target} {targets[target]['label']} (Version {fc_text}, Python {py_text})"

    if (
        len(fc_version) < 3
        or fc_version[0] != expected_fc[0]
        or fc_version[1] != expected_fc[1]
        or fc_version[2] != expected_fc[2]
    ):
        msg = (
            f"ERROR: Incompatible FreeCAD runtime version {fc_version} for target '{target}'. "
            f"{target_label} is required.\n"
        )
        log_startup(f"error-version: {fc_version} target: {target}")
        sys.stderr.write(msg)
        sys.stderr.flush()
        hard_exit(1)

    if py_ver != expected_py:
        msg = (
            f"ERROR: Incompatible Python runtime version {sys.version} for target '{target}'. "
            f"{target_label} is required.\n"
        )
        log_startup(f"error-python: {py_ver} target: {target}")
        sys.stderr.write(msg)
        sys.stderr.flush()
        hard_exit(1)

    log_startup(
        f"validated-version: {'.'.join(expected_fc)} python: {expected_py[0]}.{expected_py[1]} target: {target}"
    )

    # 3. Bootstrap freecad namespace from repository checkout
    if root not in sys.path:
        sys.path.insert(0, root)

    import freecad

    freecad_pkg_path = os.path.join(root, "freecad")
    if os.path.isdir(freecad_pkg_path) and freecad_pkg_path not in freecad.__path__:
        freecad.__path__ = [freecad_pkg_path] + list(freecad.__path__)

    # 4. Run test discovery and execution
    log_path = os.path.join(reports_dir, "tests.log")
    summary_path = os.path.join(reports_dir, "summary.json")

    log_startup("discovery-start")

    with open(log_path, "w", encoding="utf-8", buffering=1) as stream:
        spec = importlib.util.spec_from_file_location(
            "ci_test_runner", os.path.join(os.path.dirname(__file__), "run_tests.py")
        )
        test_runner = importlib.util.module_from_spec(spec)
        spec.loader.exec_module(test_runner)
        shuffle_seed = os.environ.get("FF_SHUFFLE_SEED")
        shard = os.environ.get("FF_SHARD")
        suite = test_runner.selected_suite(
            os.path.join(root, "tests"),
            os.environ.get("FF_TEST"),
            shuffle_seed=int(shuffle_seed) if shuffle_seed else None,
            shard=test_runner.parse_shard(shard) if shard else None,
        )
        runner = unittest.TextTestRunner(stream=stream, verbosity=2, resultclass=ImmediateDetailsResult)
        result = runner.run(suite)
        # Objects left by the tests (views without a GL context on Windows offscreen) must not be
        # finalized after the verdict: no garbage collection until the process ends.
        gc.disable()
        summary = {
            "tests": result.testsRun,
            "failures": len(result.failures),
            "errors": len(result.errors),
            "skipped": len(result.skipped),
            "successful": result.wasSuccessful(),
            "target": target,
        }
        exit_code = 0 if result.wasSuccessful() else 1
        with open(summary_path, "w", encoding="utf-8") as out:
            json.dump(summary, out, indent=2)
        log_startup(
            f"completed-summary: tests={result.testsRun} failures={len(result.failures)} successful={result.wasSuccessful()}"
        )
        sys.stdout.write(json.dumps(summary) + "\n")
        sys.stdout.flush()

    log_startup("exit-flush")
    sys.stdout.flush()
    sys.stderr.flush()
    if diagnostic_session is not None:
        try:
            diagnostic_session.stop()
        except Exception:
            pass
    log_startup(f"exit-now: {exit_code}")
    hard_exit(exit_code)

except BaseException as exc:
    log_startup(f"unhandled-exception: {exc}")
    traceback.print_exc()
    sys.stderr.flush()
    sys.stdout.flush()
    hard_exit(1)
